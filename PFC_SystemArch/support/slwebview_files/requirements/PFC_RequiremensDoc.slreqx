# PFC_RequiremensDoc

## PFC_RequiremensDoc: PFC_RequiremensDoc.docx への参照 (Container)
Microsoft Word ドキュメントへの読み取り専用の参照です。

### 1. 基本情報要件: 基本情報要件 (Functional)
基本情報要件
構築するPFC：Power Factor Collection Circuit(力率改善回路)は単相交流電源を入力とし、後段に接続されるインバータおよびDCDCコンバータの入力電圧として利用する直流電圧に変換するものである。
本項ではPFCに要求される事項のうち、前提条件となる情報について記載する。

#### 1.1. 使用用途　電気自動車向け充電器（オンボードチャージャー）: 使用用途 電気自動車向け充電器（オンボードチャージャー） (Informational)
使用用途 電気自動車向け充電器（オンボードチャージャー）
PFCの出力としては600Vのパワーラインに接続されたらリチウムイオン電池に接続する。PFCによって家庭用の交流電圧源から自動車駆動用のリチウムイオン電池を充電させる、いわゆるオンボードチャージャーとして利用することを用途とする。

#### 1.2. 達成したい事柄: 達成したい事柄 (Functional)

##### 1.2.1. ワールドワイド対応の入力電圧レンジ: ワールドワイド対応の入力電圧レンジ (Functional)
ワールドワイド対応の入力電圧レンジ
本ユニットが搭載される電気自動車はワールドワイド向けの車種であるため、世界で使われている全ての単相交流電圧源に対応させる必要がある。すなわち、系統電圧変動を考慮し85V~264Vacの全領域でPFC動作を行うこととする。

##### 1.2.2. 高調波規制準拠: 高調波規制準拠 (Functional)
高調波規制準拠
PFCは主に系統品質を確保するためにIEC 61000-3-2で定められた高調波規制基準を満たすように、なるべく高い力率を持って交流電圧を直流電圧に変換することを目的とする。

##### 1.2.3. 大電力: 大電力 (Functional)
大電力
より短時間で電池に充電することが望ましいため、大電力の供給が必要である。そのため可能な限り最大6kWの供給とすること。ただし、全ての入力電圧条件で6kW供給を達成しなくてもよい。世界の系統電圧のうち200V系で最低電圧である200Vac条件においては少なくとも3kW常時供給を実現し、それより低い電圧においては出力電力のレギュレーションを許容する。

##### 1.2.4. 高効率: 高効率 (Functional)
高効率
車内の居住空間を高めたいので放熱用のヒートシンク等の部品を可能な限り小型化したい。そのため、最大電力供給時PFCの電力変換効率を最低でも95%とし、コンバータ全体の損失量が150Wを超えないようにすること。
