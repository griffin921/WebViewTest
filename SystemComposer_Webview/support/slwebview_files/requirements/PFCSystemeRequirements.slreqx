# PFCSystemeRequirements

## #1: 制御ソフトウェア要件 (Functional)
制御ソフトウェアは外部からの指令を受け付ける

### #28: 入力信号 (Functional)

#### #43: 外部システムからの入力信号 (Functional)

#### #44: 回路基板からの入力信号 (Functional)

### #30: 出力信号 (Functional)

#### #45: 外部システムへの出力信号 (Functional)

#### #46: 回路基板への出力信号 (Functional)

### #37: シーケンス制御（モード切替） (Functional)

#### #41: 200V系高速充電モード (Functional)

#### #42: 100V系充電モード (Functional)

### #38: 連続時間制御 (Functional)

#### #39: 電圧制御系 (Functional)

#### #40: 電流制御系 (Functional)

#### #50: PLL（系統周波数・位相同期制御） (Functional)

## #2: 電力変換回路要件 (Functional)

### #3: 入力要件 (Functional)
後述する子要件が全て達成されていること

#### #6: 入力電圧範囲 (Functional)

#### #7: 入力電力範囲 (Functional)

#### #13: 入力電流範囲 (Functional)

### #4: 出力要件 (Functional)

#### #9: 出力電圧範囲 (Functional)

#### #10: 出力電流範囲 (Functional)

#### #11: 出力電力範囲 (Functional)

### #5: 機能要件 (Functional)

#### #14: 達成効率要件 (Functional)

#### #15: 最大許容デバイス温度条件 (Functional)

##### #24: 半導体素子 (Functional)

##### #25: 受動部品 (Functional)

###### #26: インダクタ (Functional)

###### #27: 電解コンデンサ (Functional)

### #8: ディレーティング (Functional)

#### #16: 半導体素子 (Functional)

##### #18: 電圧ディレーティング (Functional)

##### #19: 電流ディレーティング (Functional)

##### #20: 電力ディレーティング (Functional)

#### #17: 受動部品 (Functional)

##### #21: 電圧ディレーティング (Functional)

##### #22: 電流ディレーティング (Functional)

##### #23: 電力ディレーティング (Functional)

## #32: ソフトウェア実装ハードウェア要件 (Functional)

### #33: クロック (Functional)
制御周期XXusを考慮し、その時間内に少なくとも$$$ステップの処理が見積もられるため+++MHzのクロックを実現するMCUを選定すること。

### #34: AD変換 (Functional)
XXbitの分解能を持つAD変換器を有すること

### #35: PWM出力 (Functional)

#### #47: スイッチング周波数 (Functional)
100kHzでスイッチングすること

#### #48: PWM分解能 (Functional)

### #36: IOポート (Functional)
